module example-1 {

  yang-version "1.1";

  namespace "http://example.com/example-1";

  prefix "ex1";

  container greeting {

    leaf author {
      type string;
      default "John Doe";
    }
    
    leaf message {
      type string;
      default "Hello world!";
    }

  }

}
